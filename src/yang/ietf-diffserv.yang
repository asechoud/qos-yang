module ietf-diffserv {
  yang-version 1.1;
  namespace "urn:ietf:params:xml:ns:yang:ietf-diffserv";
  prefix diffserv;

  import ietf-traffic-policy {
    prefix traffic-policy;
  }
  import ietf-qos-action {
    prefix qos-action;
  }
  import ietf-inet-types {
    prefix inet;
  }
  import ietf-qos-types {
    prefix qos-types;
    reference
      "RFC XXXX: YANG Models for Quality of Service (QoS).";
  }

  organization
    "IETF Routing Area Working Group";

  contact
    "WG Web:   <https://datatracker.ietf.org/wg/rtgwg/>
     WG List:  <mailto:rtgwg@ietf.org>

     Editor:   Aseem Choudhary
               <mailto:asechoud@cisco.com>
     Editor:   Mahesh Jethanandani
               <mailto:mjethanandani@gmail.com>";

  description
    "This module contains a collection of YANG definitions for
     configuring Diffserv specification implementations.

     Copyright (c) 2023 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision YYYY-MM-DD {
    description
      "Initial version.";
    reference
      "RFC XXXX: A YANG Model for Quality of Service (QoS).";
  }

  grouping dscp {
    list dscp {
      key "min max";
      description
        "List of DSCP ranges.";
      leaf min {
        type inet:dscp;
        description
          "Minimum value of DSCP min-max range.";
      }
      leaf max {
        type inet:dscp;
        must ". >= ../min" {
          error-message
          "max must be greater than or equal to min.";
        }
        description
          "Maximum value of DSCP min-max range.";
      }
    }
    description
      "Filter grouping containing list of DSCP ranges.";
  }

  grouping source-ipv4-prefix {
    leaf-list source-ipv4-prefix {
      type inet:ipv4-prefix;
      description
        "List of source IPv4 prefixes.";
    }
    description
      "Filter grouping containing list of source IPv4 prefixes.";
  }

  grouping destination-ipv4-prefix {
    leaf-list destination-ipv4-prefix {
      type inet:ipv4-prefix;
      description
        "List of destination IPv4 prefixes.";
    }
    description
      "Filter grouping containing list of destination IPv4
       prefixes.";
  }

  grouping source-ipv6-prefix {
    leaf-list source-ipv6-prefix {
      type inet:ipv6-prefix;
      description
        "List of source IPv6 prefixes.";
    }
    description
      "Filter grouping containing list of source IPv6
       prefixes.";
  }

  grouping destination-ipv6-prefix {
    leaf-list destination-ipv6-prefix {
      type inet:ipv6-prefix;
      description
        "List of destination IPv6 prefixes.";
    }
    description
      "Filter grouping containing list of destination IPv6
       prefixes.";
  }

  grouping source-port {
    list source-port {
      key "min max";
      description
        "List of ranges of source port.";

      leaf min {
        type inet:port-number;
        description
          "Minimum value of source port range.";
      }

      leaf max {
        type inet:port-number;
        must ". >= ../min" {
          error-message
          "max must be greater than or equal to min.";
        }
        description
          "Maximum value of source port range.";
      }
    }
    description
      "Filter grouping containing list of source port ranges.";
  }

  grouping destination-port {
    list destination-port {
      key "min max";
      description
        "List of min-max range of destination ports.";
      leaf min {
        type inet:port-number;
        description
          "Minimum value of destination port.";
      }
      leaf max {
        type inet:port-number;
        must ". >= ../min" {
          error-message
          "max must be greater than or equal to min.";
        }
        description
          "Maximum value of destination port range.";
      }
    }
    description
      "Filter grouping containing list of destination port ranges.";
  }

  grouping protocol {
    list protocol {
      key "min max";
      description
        "List of ranges of protocol values. Protocol refers to the
         value in the protocol field of the IPv4 header and value
         in the 'next-header' field of IPv6 header. In IPv6 header,
         'next-header' field indicates first extension header or the
          protocol in the 'upper-layer' header.";
      reference
        "RFC 791: Internet Protocol
         RFC 8200: Internet Protocol, Version 6 (IPv6)
                   Specification.";

      leaf min {
        type inet:protocol-number;
        description
          "Minimum value of protocol range.";
      }

      leaf max {
        type inet:protocol-number;
        must ". >= ../min" {
          error-message
          "max must be greater than or equal to min.";
        }
        description
          "Maximum value of protocol range.";
      }
    }
    description
      "Filter grouping containing list of protocol ranges.";
  }

  grouping traffic-group {
    container traffic-group {
      leaf name {
        type string ;
        description
          "This leaf defines name of the traffic group referenced.";
      }
    description
      "Traffic group container.";
    }
    description
      "Traffic group grouping.";
  }

  grouping filter-match-all {
    container match-all {
      leaf action {
        type empty;
        description
          "When set, the filter matches all packets.";
      }
      description
        "The match all action.";
    }
    description
      "The match all filter grouping.";
  }

  augment "/traffic-policy:classifiers/traffic-policy:classifier" + 
          "/traffic-policy:filter" {
    choice filter-param {
      description
        "Choice of filter types.";
      case dscp {
        uses dscp;
        description
          "Filter containing list of DSCP ranges.";
      }

      case source-ipv4-prefix {
        uses source-ipv4-prefix;
        description
          "Filter containing list of source IPv4 prefixes.";
      }

      case destination-ipv4-prefix {
        uses destination-ipv4-prefix;
        description
          "Filter containing list of destination IPv4 prefix.";
      }

      case source-ipv6-prefix {
        uses source-ipv6-prefix;
        description
          "Filter containing list of source IPv6 prefixes.";
      }

      case destination-ipv6-prefix {
        uses destination-ipv6-prefix;
        description
          "Filter containing list of destination IPv6 prefix.";
      }

      case source-port {
        uses source-port;
        description
          "Filter containing list of source-port ranges.";
      }

      case destination-port {
        uses destination-port;
        description
          "Filter containing list of destination-port ranges.";
      }

      case protocol {
        uses protocol;
        description
          "Filter Type Protocol.";
      }

      case traffic-group {
        uses traffic-group;
        description
          "Filter Type traffic-group.";
      }

      case filter-match-all {
        uses filter-match-all;
        description
          "When the filter type is set to match all packets.";
      }
    }
    description
      "Augments QoS classifier to add in Diffserv filters.";
  }

  augment "/traffic-policy:policies/traffic-policy:policy" +
          "/traffic-policy:classifier/traffic-policy:inline" +
          "/traffic-policy:filter" {
    when "derived-from-or-self(../../../traffic-policy:type, " +
         "'qos-types:ipv4-diffserv-policy-type') or " +
         "derived-from-or-self(../../../traffic-policy:type, " +
         "'qos-types:ipv6-diffserv-policy-type') or " +
         "derived-from-or-self(../../../traffic-policy:type, " +
         "'qos-types:diffserv-policy-type')" {
      description
        "If policy type is v4, v6 or default Diffserv,
         this filter can be used.";
    }
    choice filter-params {
      description
        "Choice of action types.";
      case dscp {
        uses dscp;
        description
          "Filter containing list of DSCP ranges.";
      }

      case source-ipv4-prefix {
        when "derived-from-or-self(/traffic-policy:policies/" +
             "traffic-policy:policy/traffic-policy:type, " +
             "'qos-types:ipv6-diffserv-policy-type')" {
            description
               "If policy type is v6, this filter cannot be used.";
        }
        uses source-ipv4-prefix;
        description
          "Filter containing list of source IPv4 prefixes.";
      }

      case destination-ipv4-prefix {
        when "derived-from-or-self(/traffic-policy:policies" +
             "/traffic-policy:policy/traffic-policy:type, " +
             "'qos-types:ipv6-diffserv-policy-type')" {
            description
               "If policy type is v6, this filter cannot be used.";
        }
        uses destination-ipv4-prefix;
        description
          "Filter containing list of destination IPv4 prefix.";
      }

      case source-ipv6-prefix {
        when "derived-from-or-self(/traffic-policy:policies" +
             "/traffic-policy:policy/traffic-policy:type, "+
             "'qos-types:ipv4-diffserv-policy-type')" {
            description
               "If policy type is v4, this filter cannot be used.";
        }
        uses source-ipv6-prefix;
        description
          "Filter containing list of source IPv6 prefixes.";
      }

      case destination-ipv6-prefix {
        when "derived-from-or-self(/traffic-policy:policies" +
             "/traffic-policy:policy/traffic-policy:type, " +
             "'qos-types:ipv4-diffserv-policy-type')" {
            description
               "If policy type is v4, this filter cannot be used.";
        }
        uses destination-ipv6-prefix;
        description
          "Filter containing list of destination IPv6 prefix.";
      }

      case source-port {
        uses source-port;
        description
          "Filter containing list of source-port ranges.";
      }

      case destination-port {
        uses destination-port;
        description
          "Filter containing list of destination-port ranges.";
      }

      case protocol {
        uses protocol;
        description
          "Filter Type Protocol.";
      }

      case traffic-group {
        uses traffic-group;
        description
          "Filter Type traffic-group.";
      }

      case filter-match-all {
        uses filter-match-all;
        description
          "When the filter type is set to match all packets.";
      }
    }
    description
      "Augments Diffserv Classifier with common filter types.";
  }

  augment "/traffic-policy:policies/traffic-policy:policy/" +
          "traffic-policy:classifier/traffic-policy:action" {
    when "derived-from-or-self(../../traffic-policy:type, " +
         "'qos-types:ipv4-diffserv-policy-type') or " +
         "derived-from-or-self(../../traffic-policy:type, " +
         "'qos-types:ipv6-diffserv-policy-type') or " +
         "derived-from-or-self(../../traffic-policy:type, " +
         "'qos-types:diffserv-policy-type')" {
      description
        "If policy type is v4, v6 or default Diffserv,
         these actions can be used.";
    }
    description
      "Augments Diffserv Policy with action configuration.";

    choice action-params {
      description
        "Choice of different action parameters that can be taken.";

      case dscp-marking {
        uses qos-action:dscp-marking;
      }

      case meter-inline {
        uses qos-action:meter;
      }

      case meter-reference {
        uses qos-action:meter-reference;
      }

      case traffic-group-marking {
        uses qos-action:traffic-group-marking;
      }

      case child-policy {
        if-feature qos-types:child-policy;
        uses qos-action:child-policy;
      }

      case qos-count {
        if-feature qos-types:qos-count;
        uses qos-action:qos-count;
      }

      case named-qos-count {
        if-feature qos-types:named-qos-count;
        uses qos-action:named-qos-count;
      }

      case queue-inline {
        uses qos-action:queue;
      }

      case scheduler-inline {
        uses qos-action:scheduler;
      }
    }
  }
}
