module example-compb-diffserv-filter-policy {
  yang-version 1.1;
  namespace "urn:ietf:params:xml:ns:yang:" +
            "example-compb-diffserv-filter-policy";
  prefix compb-filter-policy;

  import ietf-qos-types {
    prefix qos-types;
    reference
      "RFC XXXX: YANG Models for Quality of Service (QoS).";
  }
  import ietf-traffic-policy {
    prefix traffic-policy;
  }
  import ietf-qos-action {
    prefix qos-action;
  }
  import ietf-diffserv {
    prefix diffserv;
  }

  organization
    "Company B";

  contact
    "Editor:   XYZ
               <mailto:xyz@compb.com>";

  description
    "This module contains a collection of YANG definitions for
     configuring diffserv specification implementations.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision YYYY-MM-DD {
    description
      "Initial revision of diffserv policy for Company B.";
    reference
      "RFC XXXX: YANG Data Model for QoS.";
  }


  /*************************************************
   * Classification types
   *************************************************/

  identity internal-loss-priority  {
     base qos-types:filter-type;
     description
        "Internal loss priority filter type.";
  }

  grouping loss-priority {
    list loss-priority {
      key "loss-priority";
      description
        "list of loss-priorities";
      leaf loss-priority {
        type enumeration {
          enum high {
           description "High loss Priority.";
          }
          enum medium-high {
           description "Medium to high loss priority.";
          }
          enum medium-low {
           description "Medium to low loss priority.";
          }
          enum low {
           description "Low loss priority.";
          }
        }
        description
          "Loss priority.";
      }
    }
    description
      "Filter containing list of loss priorities";
  }

  augment "/traffic-policy:policies" +
          "/traffic-policy:policy" +
          "/traffic-policy:classifier" +
          "/traffic-policy:inline/traffic-policy:filter" +
          "/diffserv:filter-params" {
    case internal-loss-priority {
        uses loss-priority;
      description
        "Filter Type Internal-loss-priority";
    }
    description 
      "Augments Diffserv Classifier with vendor " +
      "specific types.";
  }

  /*************************************************
   * Actions 
   *************************************************/

  identity mark-loss-priority {
    base qos-types:action-type;
    description
      "Mark loss-priority action type.";
  }

  grouping mark-loss-priority {
    container mark-loss-priority {
      leaf loss-priority {
        type enumeration {
          enum high {
           description "High loss Priority.";
          }
          enum medium-high {
           description "Medium to high loss priority.";
          }
          enum medium-low {
           description "Medium to low loss priority.";
          }
          enum low {
           description "Low loss priority.";
          }
        }
        description
          "Loss priority.";
      }
      description
        "Mark loss priority container.";
    }
    description
      "Mark loss priority grouping.";
  }

  augment "/traffic-policy:policies" +
          "/traffic-policy:policy" +
          "/traffic-policy:classifier" +
          "/traffic-policy:action" +
          "/diffserv:action-params" {
    case traffic-group-marking {
      uses qos-action:traffic-group-marking;
      description
        "Mark traffic group in the packet.";
    }
    case mark-loss-priority {
        uses mark-loss-priority;
      description
        "Mark loss priority in the packet.";
    }
    case meter-reference {
        uses qos-action:meter-reference;
      description
        "Assign a meter as an action.";
    }
    case discard {
        uses qos-action:discard;
      description
        "Discard action.";
    }
    case qos-count {
        uses qos-action:qos-count;
      description
        "Traffic-count action - explicit qos-count configuration.";
    }

    description 
      "Augments common diffserv policy actions";
  }
  
  augment "/qos-action:meters" +
          "/qos-action:meter" +
          "/qos-action:meter-types" +
          "/qos-action:single-rate-three-color-meter-type" +
          "/qos-action:single-rate-three-color-meter" {
     leaf one-rate-color-aware {
      type boolean;
      description
        "This defines if the meter is color-aware.";
    }
    description
      "Augmentation of color-aware flag.";
  }
  augment "/qos-action:meters" +
          "/qos-action:meter" +
          "/qos-action:meter-types" +
          "/qos-action:two-rate-three-color-meter-type" +
          "/qos-action:two-rate-three-color-meter" {
     leaf two-rate-color-aware {
      type boolean;
      description
        "This defines if the meter is color-aware.";
    }
    description
      "Augmentation of color-aware flag.";
  }
  
}
